module unique {

    namespace "urn:org:example:xml:ct:unique";
    prefix "u";

    import complex-types {
        prefix "ct"; 
    }    

    ct:complex-type ct1 {
        container c;
        ct:instance i {
            ct:instance-type ct1;
        }
    }

    ct:instance i {
        ct:instance-type ct1;

        augment "i/c" {
            container C2;
        }

        augment "i/C1" {
            container CC;
        }

        augment "i" {
            container C1;
        }

        augment "i/i/i" {
            container NEW;
        }

    }

}
