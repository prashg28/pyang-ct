module hw {

   namespace "urn:org:example:xml:ct:hw";
   prefix "hw";

   import complex-types {prefix "ct"; }

   ct:complex-type ManagedHardware {
           ct:abstract true;
           key object-id;
           leaf objectId { type string { length "1..32"; } }
           leaf serialNumber { type string; config false; }
           leaf commonName { type string; }
   }

   ct:complex-type Equipment {
           ct:extends ManagedHardware;
           ct:abstract true;
           leaf installed {type boolean; config false; }
           leaf version { type string; }
           leaf redundancy {type uint16; }
   }

   ct:complex-type EquipmentHolder {
           ct:extends ManagedHardware;
           ct:abstract true;
           ct:instance-list equipment { ct:instance-type Equipment; }
           ct:instance-list holder { ct:instance-type EquipmentHolder; }
   }

   // Holder types

   ct:complex-type Slot {
           ct:extends EquipmentHolder;
           leaf slotNumber { type uint16; config false; }
   }

   ct:complex-type Chassis {
           ct:extends EquipmentHolder;
           leaf numberOfSlots { type uint16; config false; }

   }

   // Equipment types

   ct:complex-type Card {
           ct:extends Equipment;
           leaf usedSlots { type uint16; mandatory true; }
   }

   ct:complex-type newType;

   // Root Element
    ct:instance hardware { ct:instance-type ManagedHardware; }

} // hw module
